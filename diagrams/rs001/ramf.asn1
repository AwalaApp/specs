Awala-RAMF DEFINITIONS AUTOMATIC TAGS ::=
BEGIN
  RAMFMessage ::= SEQUENCE
  {
     recipient          RAMFRecipient,
     messageId          VisibleString (SIZE(0..63)),
     creationTimeUtc    DATE-TIME,
     ttl                INTEGER (0..15552000),
     payload            OCTET STRING (SIZE(0..8388608))
  }

  RAMFRecipient ::= SEQUENCE
  {
     id                 VisibleString (SIZE(0..127)),
     internetAddress    VisibleString (SIZE(0..127)) OPTIONAL
  }
END
